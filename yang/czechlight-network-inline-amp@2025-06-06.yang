module czechlight-network-inline-amp {
    yang-version 1.1;
    namespace "http://czechlight.cesnet.cz/yang/czechlight-network-inline-amp";
    prefix cla-network-inline-amp;

    import ietf-interfaces {
        prefix if;
    }

    import czechlight-network {
        prefix cla-network;
        revision-date 2025-06-06;
    }

    description
        "This module defines constraints for network interfaces in the
         CzechLight Inline Amplifier hardware.";

    revision 2025-06-06 {
        description "Initial release.";
    }

    deviation /if:interfaces/if:interface/if:name {
        deviate add {
            must '. = "br0" or . = "eth0" or . = "eth1" or . = "oscW" or . = "oscE" or . = "sfp3"' {
                error-message "Link name must be chosen from the following options: {br0, eth0, oscW, oscE, sfp3}.";
            }
        }
    }
}
