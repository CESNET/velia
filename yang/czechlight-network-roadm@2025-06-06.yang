module czechlight-network-roadm {
    yang-version 1.1;
    namespace "http://czechlight.cesnet.cz/yang/czechlight-network-roadm";
    prefix cla-network-hardware;

    import ietf-interfaces {
        prefix if;
    }

    description
        "This module defines constraints for network interfaces in the
         CzechLight SDN ROADM hardware.";

    revision 2025-06-06 {
        description "Initial release.";
    }

    deviation /if:interfaces/if:interface/if:name {
        deviate add {
            must '. = "br0" or . = "eth0" or . = "eth1" or . = "osc"' {
                error-message "Link name must be chosen from the following options: {br0, eth0, eth1, osc}.";
            }
        }
    }
}
