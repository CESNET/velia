module czechlight-network-sdn-inline {
    yang-version 1.1;
    namespace "http://czechlight.cesnet.cz/yang/czechlight-network-sdn-inline";
    prefix cla-network-sdn-inline;

    import ietf-interfaces {
        prefix if;
    }

    import czechlight-network {
        prefix cla-network;
    }

    description
        "This module defines constraints for network interfaces in the
	 CzechLight SDN Inline Amplifier hardware.";

    revision 2025-06-06 {
        description "Initial release.";
    }

    deviation /if:interfaces/if:interface/if:name {
        deviate add {
            must '. = "br0" or . = "eth0" or . = "eth1" or . = "oscW" or . = "oscE" or . = "sfp3"' {
                error-message "Link name must be chosen from the following options: {br0, eth0, oscW, oscE, sfp3}.";
            }
        }
    }
}
