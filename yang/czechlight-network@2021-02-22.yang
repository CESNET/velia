module czechlight-network {
    yang-version 1.1;
    namespace "http://czechlight.cesnet.cz/yang/czechlight-network";
    prefix cla-network;

    import ietf-interfaces {
        prefix if;
    }

    import ietf-routing {
        prefix rt;
    }

    import ietf-ip {
        prefix ip;
    }

    import iana-if-type {
        prefix ianaift;
    }

    import ietf-ipv6-unicast-routing {
        prefix v6ur;
    }

    revision 2021-02-22 {
        description
            "Initial version. Removes interface statistics in ietf-interfaces model, removes deprecated container
             ietf-interfaces:interface-state and makes the nodes in ietf-interfaces model config false.";
    }

    // We don't support discontinuity time (yet)
    deviation /if:interfaces/if:interface/if:statistics/if:discontinuity-time { deviate not-supported; }

    // IPv6 router advertisements is not supported
    deviation /if:interfaces/if:interface/ip:ipv6/v6ur:ipv6-router-advertisements { deviate not-supported; }

    // Remove deprecated ietf-interfaces-state and ietf-routing containers. Beware, rt:routing-state references if:interfaces-state.
    deviation /rt:routing-state { deviate not-supported; }
    deviation /if:interfaces-state { deviate not-supported; }

    // As of now we implement the ietf-routing model to contain operational data only
    deviation /rt:routing { deviate add { config false; } }

    // We do not support configuring some parts of if:interfaces tree
    deviation /if:interfaces/if:interface/ip:ipv4/ip:forwarding { deviate add { config false; } }
    deviation /if:interfaces/if:interface/ip:ipv4/ip:mtu { deviate add { config false; } }
    deviation /if:interfaces/if:interface/ip:ipv4/ip:neighbor { deviate add { config false; } }
    deviation /if:interfaces/if:interface/ip:ipv6/ip:forwarding { deviate add { config false; } }
    deviation /if:interfaces/if:interface/ip:ipv6/ip:mtu { deviate add { config false; } }
    deviation /if:interfaces/if:interface/ip:ipv6/ip:neighbor { deviate add { config false; } }
    deviation /if:interfaces/if:interface/ip:ipv6/ip:dup-addr-detect-transmits { deviate add { config false; } }

    // User should not create new links or reconfigure link types
    deviation /if:interfaces/if:interface/if:name {
        deviate add {
            must '. = "br0" or . = "eth0" or . = "eth1" or . = "eth2" or . = "osc" or . = "oscW" or . = "oscE" or . = "sfp3"' {
                error-message "Link name must be chosen from the following options: {br0, eth0, eth1, osc, oscW, oscE, sfp3}.";
            }
        }
    }

    deviation /if:interfaces/if:interface/if:type {
        deviate add {
            must 'not(re-match(../if:name, "br\d+")) or . = "ianaift:bridge"' {
                error-message "The if:type of a 'br*' interface must be set to ianaift:bridge";
            }

            must 'not(re-match(../if:name, "eth\d+")) or . = "ianaift:ethernetCsmacd"' {
                error-message "The if:type of a 'eth*' interface must be set to ianaift:ethernetCsmacd";
            }

            must 'not(re-match(../if:name, "osc.*")) or . = "ianaift:ethernetCsmacd"' {
                error-message "The if:type of a 'osc*' interface must be set to ianaift:ethernetCsmacd";
            }

            must 'not(re-match(../if:name, "sfp.*")) or . = "ianaift:ethernetCsmacd"' {
                error-message "The if:type of a 'sfp*' interface must be set to ianaift:ethernetCsmacd";
            }
        }
    }

    augment /if:interfaces/if:interface {
        description "Add the option to add this link to a bridge.";

        leaf bridge {
            must '../if:type = "ianaift:ethernetCsmacd"' {
                error-message "Only ethernet interfaces can be enslaved to a bridge.";
            }

            must '/if:interfaces/if:interface[if:name = current()]/if:type = "ianaift:bridge"' {
                error-message "An interface can be only enslaved to a bridge";
            }

            must '(not(../ip:ipv4) or ../ip:ipv4/ip:enabled[.="false"]) and
                  (not(../ip:ipv6) or ../ip:ipv6/ip:enabled[.="false"])' {
                error-message "IP protocols must be disabled for enslaved link.";
            }

            type if:interface-ref;
            mandatory false;
            description "The name of the bridge to add the link to.";
        }
    }

    // Make it hard to accidentally lose connection by removing ipv4/ipv6 presence containers or all IP addresses
    deviation /if:interfaces/if:interface {
        deviate add {
            must 'if:enabled = "false" or
                  ip:ipv4/ip:enabled = "true" or
                  ip:ipv6/ip:enabled = "true" or
                  cla-network:bridge' {
                error-message "Enabled interface must always have at least one protocol active or it must be connected in the bridge.";
            }
        }

        deviate add {
            must 'if:type != "ianaift:bridge" or
                  (if:enabled != "true") or
                  (count(../if:interface[(if:enabled = "true") and (cla-network:bridge = current()/name)]) > 0)' {
                error-message "All enabled bridges must have at least one enabled enslaved interface";
            }
        }
    }

    augment /if:interfaces/if:interface/ip:ipv4 {
        description "Add the IPv4 autoconfiguration option (DHCP client).";

        leaf dhcp-client {
            type boolean;
            default true;
            description "Enable DHCP client.";
        }
    }

    deviation /if:interfaces/if:interface/ip:ipv4 {
        deviate add {
            must 'ip:enabled = "false" or ../if:enabled = "false" or count(ip:address) > 0 or cla-network:dhcp-client = "true"' {
                error-message "There must always be at least one IPv4 address or the autoconfiguration must be turned on unless the interface or protocol is disabled.";
            }
        }
    }

    deviation /if:interfaces/if:interface/ip:ipv6 {
        deviate add {
            must 'ip:enabled = "false" or ../if:enabled = "false" or count(ip:address) > 0 or ip:autoconf/ip:create-global-addresses = "true"' {
                error-message "There must always be at least one IPv6 address or the autoconfiguration must be turned on unless the interface or protocol is disabled.";
            }
        }
    }

    identity dhcp {
        base rt:routing-protocol;
        description "Identity for route installed by DHCP.";
    }
    identity ra {
        base rt:routing-protocol;
        description "Identity for route installed by router advertisement.";
    }
}
