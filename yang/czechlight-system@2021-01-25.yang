module czechlight-system {
  yang-version 1.1;
  namespace
    "http://czechlight.cesnet.cz/yang/czechlight-system";

  prefix "cla-sys";

  import ietf-yang-types {
    prefix yang;
  }

  organization "CESNET";
  contact "photonic@cesnet.cz";
  description
    "YANG model for system administration in Czechlight devices.";

  revision 2021-01-25 {
    description "Adding firmware slot list.";
  }

  revision 2021-01-13 {
    description "Initial release";
  }

  container firmware {
    config false;

    list firmware-slot {
      description "Stores information about firmware slots.";

      key name;

      leaf name {
        description "Name of the firmware slot.";
        type string;
      }

      leaf version {
        description "Version of the firmware installed in the slot.";
        type string;
      }

      leaf state {
        description "Current state of the firmware slot.";
        type enumeration {
          enum unknown;
          enum inactive;
          enum booted;
        }
      }

      leaf installed {
        description "Stores the date of firmware installation into this slot.";
        type yang:date-and-time;
      }
    }

    container installation {
      leaf status {
        description "Informs about the status of the current (or last) installation.";

        type enumeration {
          enum none;
          enum in-progress;
          enum succeeded;
          enum failed;
        }
      }

      leaf message {
        description "The last message from the installation process. This MAY contain the last error message.";
        type string;
      }

      notification update {
        description "Notifies clients about installation progress.";

        leaf message {
          description "Progress status.";
          type string;
        }

        leaf progress {
          description "Progress of the installation in percents.";

          type int8 {
            range "0 .. 100";
          }
        }
      }

      action install {
        input {
          leaf url {
            description "URL or path to the new firmware.";
            type string;
            mandatory true;
          }
        }
      }
    }
  }
}
